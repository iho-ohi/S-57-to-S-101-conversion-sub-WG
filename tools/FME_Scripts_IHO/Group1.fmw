FME workspace Group1.fmw

Parameters:
- SourceDataset_S57 = xxxxxx\*.*   # Source S-57 (ENC) Hydrographic Data File(s)
- DestDataset_SHAPEFILE = xxxxxx   # Destination Esri Shapefile Folder
- DestDataset_XLSXW = LOKBSN.xlsx   # Destination Microsoft Excel File
- DestDataset_XLSXW_9 = FLODOC.xlsx   # Destination Microsoft Excel File
- DestDataset_XLSXW_7 = PONTON.xlsx   # Destination Microsoft Excel File
- DestDataset_XLSXW_6 = DOCARE.xlsx   # Destination Microsoft Excel File
- DestDataset_XLSXW_8 = HULKES.xlsx   # Destination Microsoft Excel File

Readers:
- S57_1: S57 from $(SourceDataset_S57)

Writers:
- SHAPEFILE_1: SHAPEFILE to $(DestDataset_SHAPEFILE)
- XLSXW_1: XLSXW to $(DestDataset_XLSXW)
- XLSXW_2: XLSXW to $(DestDataset_XLSXW_9)
- XLSXW_3: XLSXW to $(DestDataset_XLSXW_7)
- XLSXW_4: XLSXW to $(DestDataset_XLSXW_6)
- XLSXW_5: XLSXW to $(DestDataset_XLSXW_8)

Note: Features that start/stop being Group 1 between S-57 and S-101
Note: Extracts the ENC name so we can trace where / the features come from
Note: The paths to the ENC data, as well as the resulting .SHP and .XLS have been disabled. / They can be changed easily on the Navigator Window to the left.
Note: Saves the features to Excel. / The Geometry Remover makes sure no / coordinate data will be saved to Excel.
GeometryRemover_2
    -> FLODOC (writer XLSXW_2)
FLODOC (writer XLSXW_2)
    attributes: RCID number(20), PRIM number(20), GRUP number(20), OBJL number(20), RVER number(20), AGEN number(20), FIDN number(20), FIDS number(20), LNAM string(16), LNAM_REFS__ string(16), FFPT_RIND__ number(20), COLOUR string(254), COLPAT string(254), CONDTN number(20), CONRAD number(20), CONVIS number(20), DATEND string(254), DATSTA string(254), DRVAL1 number(20), HORACC number(20), HORCLR number(20), HORLEN number(20), HORWID number(20), LIFCAP number(20), NOBJNM string(254), OBJNAM string(254), STATUS string(254), VERACC number(20), VERLEN number(20), VERDAT number(20),
      INFORM string(254), NINFOM string(254), NTXTDS string(254), PICREP string(254), SCAMAX number(20), SCAMIN number(20), TXTDSC string(254), RECDAT string(254), RECIND string(254), SORDAT string(254), SORIND string(254), DSNM string(12)
GeometryFilter
    BREAK_AGG = Yes
    GEOM_PORT_NAMES = Line Area
    INSTANTIATE = Yes
    LINE -> FLODOC_line (writer SHAPEFILE_1)
    AREA -> FLODOC_polygon (writer SHAPEFILE_1)
GeometryRemover_3
    -> PONTON (writer XLSXW_3)
PONTON (writer XLSXW_3)
    attributes: RCID number(20), PRIM number(20), GRUP number(20), OBJL number(20), RVER number(20), AGEN number(20), FIDN number(20), FIDS number(20), LNAM string(16), LNAM_REFS__ string(16), FFPT_RIND__ number(20), CONDTN number(20), CONRAD number(20), CONVIS number(20), DATEND string(254), DATSTA string(254), NATCON string(254), NOBJNM string(254), OBJNAM string(254), PEREND string(254), PERSTA string(254), STATUS string(254), VERACC number(20), VERLEN number(20), INFORM string(254), NINFOM string(254), NTXTDS string(254), SCAMAX number(20), SCAMIN number(20), TXTDSC string(254),
      RECDAT string(254), RECIND string(254), SORDAT string(254), SORIND string(254), DSNM string(12)
GeometryFilter_3
    BREAK_AGG = Yes
    GEOM_PORT_NAMES = Line Area
    INSTANTIATE = Yes
    LINE -> PONTON_line (writer SHAPEFILE_1)
    AREA -> PONTON_polygon (writer SHAPEFILE_1)
GeometryRemover_4
    -> DOCARE (writer XLSXW_4)
DOCARE (writer XLSXW_4)
    attributes: RCID number(20), PRIM number(20), GRUP number(20), OBJL number(20), RVER number(20), AGEN number(20), FIDN number(20), FIDS number(20), LNAM string(16), LNAM_REFS__ string(16), FFPT_RIND__ number(20), CATDOC number(20), CONDTN number(20), DATEND string(254), DATSTA string(254), HORACC number(20), HORCLR number(20), NOBJNM string(254), OBJNAM string(254), STATUS string(254), INFORM string(254), NINFOM string(254), NTXTDS string(254), SCAMAX number(20), SCAMIN number(20), TXTDSC string(254), RECDAT string(254), RECIND string(254), SORDAT string(254), SORIND string(254),
      DSNM string(12)
GeometryRemover_5
    -> HULKES (writer XLSXW_5)
HULKES (writer XLSXW_5)
    attributes: RCID number(20), PRIM number(20), GRUP number(20), OBJL number(20), RVER number(20), AGEN number(20), FIDN number(20), FIDS number(20), LNAM string(16), LNAM_REFS__ string(16), FFPT_RIND__ number(20), CATHLK string(254), COLOUR string(254), COLPAT string(254), CONRAD number(20), CONVIS number(20), HORACC number(20), HORLEN number(20), HORWID number(20), NOBJNM string(254), OBJNAM string(254), VERACC number(20), VERLEN number(20), CONDTN number(20), INFORM string(254), NINFOM string(254), NTXTDS string(254), PICREP string(254), SCAMAX number(20), SCAMIN number(20),
      TXTDSC string(254), RECDAT string(254), RECIND string(254), SORDAT string(254), SORIND string(254), DSNM string(12)
GeometryFilter_2
    BREAK_AGG = Yes
    GEOM_PORT_NAMES = Point Area
    INSTANTIATE = Yes
    POINT -> HULKES_point (writer SHAPEFILE_1)
    AREA -> HULKES_polygon (writer SHAPEFILE_1)

Bookmark: Reader Feature Types
LOKBSN (reader S57_1)
    attributes: RCID integer, PRIM integer16, GRUP integer16, OBJL integer, RVER integer16, AGEN integer, FIDN integer, FIDS integer, LNAM char(16), LNAM_REFS{} char(16), FFPT_RIND{} integer16, DATEND char(254), DATSTA char(254), HORACC double, HORCLR double, HORLEN double, HORWID double, NOBJNM char(254), OBJNAM char(254), STATUS char(254), INFORM char(254), NINFOM char(254), NTXTDS char(254), SCAMAX integer, SCAMIN integer, TXTDSC char(254), RECDAT char(254), RECIND char(254), SORDAT char(254), SORIND char(254)
    -> FilenamePartExtractor
FLODOC (reader S57_1)
    attributes: RCID integer, PRIM integer16, GRUP integer16, OBJL integer, RVER integer16, AGEN integer, FIDN integer, FIDS integer, LNAM char(16), LNAM_REFS{} char(16), FFPT_RIND{} integer16, COLOUR char(254), COLPAT char(254), CONDTN integer, CONRAD integer, CONVIS integer, DATEND char(254), DATSTA char(254), DRVAL1 double, HORACC double, HORCLR double, HORLEN double, HORWID double, LIFCAP double, NOBJNM char(254), OBJNAM char(254), STATUS char(254), VERACC double, VERLEN double, VERDAT integer,
      INFORM char(254), NINFOM char(254), NTXTDS char(254), PICREP char(254), SCAMAX integer, SCAMIN integer, TXTDSC char(254), RECDAT char(254), RECIND char(254), SORDAT char(254), SORIND char(254)
    -> FilenamePartExtractor_2
PONTON (reader S57_1)
    attributes: RCID integer, PRIM integer16, GRUP integer16, OBJL integer, RVER integer16, AGEN integer, FIDN integer, FIDS integer, LNAM char(16), LNAM_REFS{} char(16), FFPT_RIND{} integer16, CONDTN integer, CONRAD integer, CONVIS integer, DATEND char(254), DATSTA char(254), NATCON char(254), NOBJNM char(254), OBJNAM char(254), PEREND char(254), PERSTA char(254), STATUS char(254), VERACC double, VERLEN double, INFORM char(254), NINFOM char(254), NTXTDS char(254), SCAMAX integer, SCAMIN integer, TXTDSC char(254),
      RECDAT char(254), RECIND char(254), SORDAT char(254), SORIND char(254)
    -> FilenamePartExtractor_3
DOCARE (reader S57_1)
    attributes: RCID integer, PRIM integer16, GRUP integer16, OBJL integer, RVER integer16, AGEN integer, FIDN integer, FIDS integer, LNAM char(16), LNAM_REFS{} char(16), FFPT_RIND{} integer16, CATDOC integer, CONDTN integer, DATEND char(254), DATSTA char(254), HORACC double, HORCLR double, NOBJNM char(254), OBJNAM char(254), STATUS char(254), INFORM char(254), NINFOM char(254), NTXTDS char(254), SCAMAX integer, SCAMIN integer, TXTDSC char(254), RECDAT char(254), RECIND char(254), SORDAT char(254), SORIND char(254)
    -> FilenamePartExtractor_4
HULKES (reader S57_1)
    attributes: RCID integer, PRIM integer16, GRUP integer16, OBJL integer, RVER integer16, AGEN integer, FIDN integer, FIDS integer, LNAM char(16), LNAM_REFS{} char(16), FFPT_RIND{} integer16, CATHLK char(254), COLOUR char(254), COLPAT char(254), CONRAD integer, CONVIS integer, HORACC double, HORLEN double, HORWID double, NOBJNM char(254), OBJNAM char(254), VERACC double, VERLEN double, CONDTN integer, INFORM char(254), NINFOM char(254), NTXTDS char(254), PICREP char(254), SCAMAX integer, SCAMIN integer,
      TXTDSC char(254), RECDAT char(254), RECIND char(254), SORDAT char(254), SORIND char(254)
    -> FilenamePartExtractor_5

Bookmark: Filename Extractor
FilenamePartExtractor
    SRC_ATTR = @Value(DSNM)
    -> LOKBSN (writer SHAPEFILE_1)
    -> GeometryRemover
FilenamePartExtractor_2
    SRC_ATTR = @Value(DSNM)
    -> GeometryFilter
    -> GeometryRemover_2
FilenamePartExtractor_3
    SRC_ATTR = @Value(DSNM)
    -> GeometryFilter_3
    -> GeometryRemover_3
FilenamePartExtractor_4
    SRC_ATTR = @Value(DSNM)
    -> DOCARE (writer SHAPEFILE_1)
    -> GeometryRemover_4
FilenamePartExtractor_5
    SRC_ATTR = @Value(DSNM)
    -> GeometryFilter_2
    -> GeometryRemover_5

Bookmark: Excel Table
GeometryRemover
    -> LOKBSN.xlsx (writer XLSXW_1)
LOKBSN.xlsx (writer XLSXW_1)
    attributes: RCID number(20), PRIM number(20), GRUP number(20), OBJL number(20), RVER number(20), AGEN number(20), FIDN number(20), FIDS number(20), LNAM string(16), LNAM_REFS__ string(16), FFPT_RIND__ number(20), DATEND string(254), DATSTA string(254), HORACC number(20), HORCLR number(20), HORLEN number(20), HORWID number(20), NOBJNM string(254), OBJNAM string(254), STATUS string(254), INFORM string(254), NINFOM string(254), NTXTDS string(254), SCAMAX number(20), SCAMIN number(20), TXTDSC string(254), RECDAT string(254), RECIND string(254), SORDAT string(254), SORIND string(254),
      DSNM string(12)

Bookmark: Writer Feature Types
LOKBSN (writer SHAPEFILE_1)
    attributes: RCID long, PRIM short, GRUP short, OBJL long, RVER short, AGEN long, FIDN long, FIDS long, LNAM char(16), LNAM_REFS_ char(16), FFPT_RIND_ short, DATEND char(254), DATSTA char(254), HORACC double, HORCLR double, HORLEN double, HORWID double, NOBJNM char(254), OBJNAM char(254), STATUS char(254), INFORM char(254), NINFOM char(254), NTXTDS char(254), SCAMAX long, SCAMIN long, TXTDSC char(254), RECDAT char(254), RECIND char(254), SORDAT char(254), SORIND char(254),
      DSNM char(12)
FLODOC_line (writer SHAPEFILE_1)
    attributes: RCID long, PRIM short, GRUP short, OBJL long, RVER short, AGEN long, FIDN long, FIDS long, LNAM char(16), LNAM_REFS_ char(16), FFPT_RIND_ short, COLOUR char(254), COLPAT char(254), CONDTN long, CONRAD long, CONVIS long, DATEND char(254), DATSTA char(254), DRVAL1 double, HORACC double, HORCLR double, HORLEN double, HORWID double, LIFCAP double, NOBJNM char(254), OBJNAM char(254), STATUS char(254), VERACC double, VERLEN double, VERDAT long,
      INFORM char(254), NINFOM char(254), NTXTDS char(254), PICREP char(254), SCAMAX long, SCAMIN long, TXTDSC char(254), RECDAT char(254), RECIND char(254), SORDAT char(254), SORIND char(254), DSNM char(12)
FLODOC_polygon (writer SHAPEFILE_1)
    attributes: RCID long, PRIM short, GRUP short, OBJL long, RVER short, AGEN long, FIDN long, FIDS long, LNAM char(16), LNAM_REFS_ char(16), FFPT_RIND_ short, COLOUR char(254), COLPAT char(254), CONDTN long, CONRAD long, CONVIS long, DATEND char(254), DATSTA char(254), DRVAL1 double, HORACC double, HORCLR double, HORLEN double, HORWID double, LIFCAP double, NOBJNM char(254), OBJNAM char(254), STATUS char(254), VERACC double, VERLEN double, VERDAT long,
      INFORM char(254), NINFOM char(254), NTXTDS char(254), PICREP char(254), SCAMAX long, SCAMIN long, TXTDSC char(254), RECDAT char(254), RECIND char(254), SORDAT char(254), SORIND char(254), DSNM char(12)
PONTON_line (writer SHAPEFILE_1)
    attributes: RCID long, PRIM short, GRUP short, OBJL long, RVER short, AGEN long, FIDN long, FIDS long, LNAM char(16), LNAM_REFS_ char(16), FFPT_RIND_ short, CONDTN long, CONRAD long, CONVIS long, DATEND char(254), DATSTA char(254), NATCON char(254), NOBJNM char(254), OBJNAM char(254), PEREND char(254), PERSTA char(254), STATUS char(254), VERACC double, VERLEN double, INFORM char(254), NINFOM char(254), NTXTDS char(254), SCAMAX long, SCAMIN long, TXTDSC char(254),
      RECDAT char(254), RECIND char(254), SORDAT char(254), SORIND char(254), DSNM char(12)
PONTON_polygon (writer SHAPEFILE_1)
    attributes: RCID long, PRIM short, GRUP short, OBJL long, RVER short, AGEN long, FIDN long, FIDS long, LNAM char(16), LNAM_REFS_ char(16), FFPT_RIND_ short, CONDTN long, CONRAD long, CONVIS long, DATEND char(254), DATSTA char(254), NATCON char(254), NOBJNM char(254), OBJNAM char(254), PEREND char(254), PERSTA char(254), STATUS char(254), VERACC double, VERLEN double, INFORM char(254), NINFOM char(254), NTXTDS char(254), SCAMAX long, SCAMIN long, TXTDSC char(254),
      RECDAT char(254), RECIND char(254), SORDAT char(254), SORIND char(254), DSNM char(12)
DOCARE (writer SHAPEFILE_1)
    attributes: RCID long, PRIM short, GRUP short, OBJL long, RVER short, AGEN long, FIDN long, FIDS long, LNAM char(16), LNAM_REFS_ char(16), FFPT_RIND_ short, CATDOC long, CONDTN long, DATEND char(254), DATSTA char(254), HORACC double, HORCLR double, NOBJNM char(254), OBJNAM char(254), STATUS char(254), INFORM char(254), NINFOM char(254), NTXTDS char(254), SCAMAX long, SCAMIN long, TXTDSC char(254), RECDAT char(254), RECIND char(254), SORDAT char(254), SORIND char(254),
      DSNM char(12)
HULKES_point (writer SHAPEFILE_1)
    attributes: RCID long, PRIM short, GRUP short, OBJL long, RVER short, AGEN long, FIDN long, FIDS long, LNAM char(16), LNAM_REFS_ char(16), FFPT_RIND_ short, CATHLK char(254), COLOUR char(254), COLPAT char(254), CONRAD long, CONVIS long, HORACC double, HORLEN double, HORWID double, NOBJNM char(254), OBJNAM char(254), VERACC double, VERLEN double, CONDTN long, INFORM char(254), NINFOM char(254), NTXTDS char(254), PICREP char(254), SCAMAX long, SCAMIN long,
      TXTDSC char(254), RECDAT char(254), RECIND char(254), SORDAT char(254), SORIND char(254), DSNM char(12)
HULKES_polygon (writer SHAPEFILE_1)
    attributes: RCID long, PRIM short, GRUP short, OBJL long, RVER short, AGEN long, FIDN long, FIDS long, LNAM char(16), LNAM_REFS_ char(16), FFPT_RIND_ short, CATHLK char(254), COLOUR char(254), COLPAT char(254), CONRAD long, CONVIS long, HORACC double, HORLEN double, HORWID double, NOBJNM char(254), OBJNAM char(254), VERACC double, VERLEN double, CONDTN long, INFORM char(254), NINFOM char(254), NTXTDS char(254), PICREP char(254), SCAMAX long, SCAMIN long,
      TXTDSC char(254), RECDAT char(254), RECIND char(254), SORDAT char(254), SORIND char(254), DSNM char(12)
