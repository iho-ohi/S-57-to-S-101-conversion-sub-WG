FME workspace InTheWater.fmw

Parameters:
- SourceDataset_S57 = xxxxxxxx\*.*   # Source S-57 (ENC) Hydrographic Data File(s)
- DestDataset_SHAPEFILE = xxxxxx   # Destination Esri Shapefile Folder
- SourceDataset_S57_3 = xxxxxxx\*.*   # Source S-57 (ENC) Hydrographic Data File(s)
- DestDataset_XLSXW = BUISGL.xlsx   # Destination Microsoft Excel File
- DestDataset_XLSXW_9 = SILTNK.xlsx   # Destination Microsoft Excel File
- DestDataset_XLSXW_7 = LNDMRK.xlsx   # Destination Microsoft Excel File
- DestDataset_XLSXW_6 = FORSTC.xlsx   # Destination Microsoft Excel File
- DestDataset_XLSXW_8 = CRANES.xlsx   # Destination Microsoft Excel File

Readers:
- S57_1: S57 from $(SourceDataset_S57)
- S57_2: S57 from $(SourceDataset_S57_3)

Writers:
- SHAPEFILE_1: SHAPEFILE to $(DestDataset_SHAPEFILE)
- XLSXW_1: XLSXW to $(DestDataset_XLSXW)
- XLSXW_2: XLSXW to $(DestDataset_XLSXW_9)
- XLSXW_3: XLSXW to $(DestDataset_XLSXW_7)
- XLSXW_4: XLSXW to $(DestDataset_XLSXW_6)
- XLSXW_5: XLSXW to $(DestDataset_XLSXW_8)

Note: S-57 features to we want to find / out if they are "in the water"
Junction
    -> AttributeRemover_6
Note: Removes the attributes from the navigable features we are not interested in from the resulting .shp/.xls
Note: The paths to the ENC data, as well as the resulting .SHP and .XLS have been disabled. / They can be changed easily on the Navigator Window to the left.
Note: Filters the target features according to intersecting the navigable features
Note: Extracts the ENC name so we can trace where / the features come from
AttributeRemover_6
    REMOVE_ATTRS = AGEN,CATHLK,COLOUR,COLPAT,CONDTN,CONRAD,CONVIS,DATEND,DATSTA,DRVAL1,DRVAL2,DSNM,FFPT_RIND{0},FIDN,FIDS,GRUP,HORACC,HORCLR,HORLEN,HORWID,INFORM,LIFCAP,LNAM,LNAM_REFS{0},NATCON,NINFOM,NOBJNM,NTXTDS,OBJL,OBJNAM,PEREND,PERSTA,PICREP,PRIM,QUASOU,RCID,RECDAT,RECIND,RESTRN,RVER,SCAMAX,SCAMIN,SORDAT,SORIND,SOUACC,STATUS,TECSOU,TXTDSC,VERACC,VERDAT,VERLEN
    -> SpatialFilter_5 [Filter]
    -> SpatialFilter_4 [Filter]
    -> SpatialFilter [Filter]
    -> SpatialFilter_3 [Filter]
    -> SpatialFilter_2 [Filter]
Note: Removes unnecessary attributes
Note: Saves the features to Excel. / The Geometry Remover makes sure no / coordinate data will be saved to Excel.
GeometryFilter_4
    BREAK_AGG = Yes
    GEOM_PORT_NAMES = Point Line Area
    INSTANTIATE = Yes
    POINT -> LNDMRK_point (writer SHAPEFILE_1)
    LINE -> LNDMRK_line (writer SHAPEFILE_1)
    AREA -> LNDMRK_polygon (writer SHAPEFILE_1)
GeometryRemover_2
    -> BUISGL (writer XLSXW_1)
BUISGL (writer XLSXW_1)
    attributes: RCID number(20), PRIM number(20), GRUP number(20), OBJL number(20), RVER number(20), AGEN number(20), FIDN number(20), FIDS number(20), LNAM string(16), LNAM_REFS__ string(16), FFPT_RIND__ number(20), CATLMK string(254), COLOUR string(254), COLPAT string(254), CONDTN number(20), CONRAD number(20), CONVIS number(20), ELEVAT number(20), FUNCTN string(254), HEIGHT number(20), NATCON string(254), NOBJNM string(254), OBJNAM string(254), STATUS string(254), VERACC number(20), VERDAT number(20), VERLEN number(20), INFORM string(254), NINFOM string(254), NTXTDS string(254),
      PICREP string(254), SCAMAX number(20), SCAMIN number(20), TXTDSC string(254), RECDAT string(254), RECIND string(254), SORDAT string(254), SORIND string(254), DSNM string(12)
GeometryFilter
    BREAK_AGG = Yes
    GEOM_PORT_NAMES = Point Area
    INSTANTIATE = Yes
    POINT -> BUISGL_point (writer SHAPEFILE_1)
    AREA -> BUISGL_polygon (writer SHAPEFILE_1)
GeometryRemover_3
    -> SILTNK (writer XLSXW_2)
SILTNK (writer XLSXW_2)
    attributes: RCID number(20), PRIM number(20), GRUP number(20), OBJL number(20), RVER number(20), AGEN number(20), FIDN number(20), FIDS number(20), LNAM string(16), LNAM_REFS__ string(16), FFPT_RIND__ number(20), CATLMK string(254), COLOUR string(254), COLPAT string(254), CONDTN number(20), CONRAD number(20), CONVIS number(20), ELEVAT number(20), FUNCTN string(254), HEIGHT number(20), NATCON string(254), NOBJNM string(254), OBJNAM string(254), STATUS string(254), VERACC number(20), VERDAT number(20), VERLEN number(20), INFORM string(254), NINFOM string(254), NTXTDS string(254),
      PICREP string(254), SCAMAX number(20), SCAMIN number(20), TXTDSC string(254), RECDAT string(254), RECIND string(254), SORDAT string(254), SORIND string(254), DSNM string(12)
GeometryFilter_5
    BREAK_AGG = Yes
    GEOM_PORT_NAMES = Point Area
    INSTANTIATE = Yes
    POINT -> SILTNK_point (writer SHAPEFILE_1)
    AREA -> SILTNK_polygon (writer SHAPEFILE_1)
GeometryRemover_4
    -> FORSTC (writer XLSXW_4)
FORSTC (writer XLSXW_4)
    attributes: RCID number(20), PRIM number(20), GRUP number(20), OBJL number(20), RVER number(20), AGEN number(20), FIDN number(20), FIDS number(20), LNAM string(16), LNAM_REFS__ string(16), FFPT_RIND__ number(20), CATFOR number(20), CONDTN number(20), CONRAD number(20), CONVIS number(20), HEIGHT number(20), NATCON string(254), NOBJNM string(254), OBJNAM string(254), VERACC number(20), VERDAT number(20), VERLEN number(20), INFORM string(254), NINFOM string(254), NTXTDS string(254), PICREP string(254), SCAMAX number(20), SCAMIN number(20), TXTDSC string(254), RECDAT string(254),
      RECIND string(254), SORDAT string(254), SORIND string(254), DSNM string(12)
GeometryFilter_3
    BREAK_AGG = Yes
    GEOM_PORT_NAMES = Point Line Area
    INSTANTIATE = Yes
    POINT -> FORSTC_point (writer SHAPEFILE_1)
    LINE -> FORSTC_line (writer SHAPEFILE_1)
    AREA -> FORSTC_polygon (writer SHAPEFILE_1)
GeometryRemover_5
    -> CRANES (writer XLSXW_5)
CRANES (writer XLSXW_5)
    attributes: RCID number(20), PRIM number(20), GRUP number(20), OBJL number(20), RVER number(20), AGEN number(20), FIDN number(20), FIDS number(20), LNAM string(16), LNAM_REFS__ string(16), FFPT_RIND__ number(20), CATCRN number(20), COLOUR string(254), COLPAT string(254), CONDTN number(20), CONRAD number(20), CONVIS number(20), HEIGHT number(20), LIFCAP number(20), NOBJNM string(254), OBJNAM string(254), ORIENT number(20), RADIUS number(20), STATUS string(254), VERACC number(20), VERCLR number(20), VERDAT number(20), VERLEN number(20), INFORM string(254), NINFOM string(254),
      NTXTDS string(254), PICREP string(254), SCAMAX number(20), SCAMIN number(20), TXTDSC string(254), RECDAT string(254), RECIND string(254), SORDAT string(254), SORIND string(254), DSNM string(12)
GeometryFilter_2
    BREAK_AGG = Yes
    GEOM_PORT_NAMES = Point Area
    INSTANTIATE = Yes
    POINT -> CRANES_point (writer SHAPEFILE_1)
    AREA -> CRANES_polygon (writer SHAPEFILE_1)

Bookmark: Navigable Features
DEPARE (reader S57_2)
    attributes: RCID integer, PRIM integer16, GRUP integer16, OBJL integer, RVER integer16, AGEN integer, FIDN integer, FIDS integer, LNAM char(16), LNAM_REFS{} char(16), FFPT_RIND{} integer16, DRVAL1 double, DRVAL2 double, QUASOU char(254), SOUACC double, VERDAT integer, INFORM char(254), NINFOM char(254), NTXTDS char(254), SCAMAX integer, SCAMIN integer, TXTDSC char(254), RECDAT char(254), RECIND char(254), SORDAT char(254), SORIND char(254)
    -> Junction
DRGARE (reader S57_2)
    attributes: RCID integer, PRIM integer16, GRUP integer16, OBJL integer, RVER integer16, AGEN integer, FIDN integer, FIDS integer, LNAM char(16), LNAM_REFS{} char(16), FFPT_RIND{} integer16, DRVAL1 double, DRVAL2 double, NOBJNM char(254), OBJNAM char(254), QUASOU char(254), RESTRN char(254), SOUACC double, TECSOU char(254), VERDAT integer, INFORM char(254), NINFOM char(254), NTXTDS char(254), SCAMAX integer, SCAMIN integer, TXTDSC char(254), RECDAT char(254), RECIND char(254), SORDAT char(254), SORIND char(254)
    -> Junction
FLODOC (reader S57_2)
    attributes: RCID integer, PRIM integer16, GRUP integer16, OBJL integer, RVER integer16, AGEN integer, FIDN integer, FIDS integer, LNAM char(16), LNAM_REFS{} char(16), FFPT_RIND{} integer16, COLOUR char(254), COLPAT char(254), CONDTN integer, CONRAD integer, CONVIS integer, DATEND char(254), DATSTA char(254), DRVAL1 double, HORACC double, HORCLR double, HORLEN double, HORWID double, LIFCAP double, NOBJNM char(254), OBJNAM char(254), STATUS char(254), VERACC double, VERLEN double, VERDAT integer,
      INFORM char(254), NINFOM char(254), NTXTDS char(254), PICREP char(254), SCAMAX integer, SCAMIN integer, TXTDSC char(254), RECDAT char(254), RECIND char(254), SORDAT char(254), SORIND char(254)
    -> Junction
HULKES (reader S57_2)
    attributes: RCID integer, PRIM integer16, GRUP integer16, OBJL integer, RVER integer16, AGEN integer, FIDN integer, FIDS integer, LNAM char(16), LNAM_REFS{} char(16), FFPT_RIND{} integer16, CATHLK char(254), COLOUR char(254), COLPAT char(254), CONRAD integer, CONVIS integer, HORACC double, HORLEN double, HORWID double, NOBJNM char(254), OBJNAM char(254), VERACC double, VERLEN double, CONDTN integer, INFORM char(254), NINFOM char(254), NTXTDS char(254), PICREP char(254), SCAMAX integer, SCAMIN integer,
      TXTDSC char(254), RECDAT char(254), RECIND char(254), SORDAT char(254), SORIND char(254)
    -> Junction
PONTON (reader S57_2)
    attributes: RCID integer, PRIM integer16, GRUP integer16, OBJL integer, RVER integer16, AGEN integer, FIDN integer, FIDS integer, LNAM char(16), LNAM_REFS{} char(16), FFPT_RIND{} integer16, CONDTN integer, CONRAD integer, CONVIS integer, DATEND char(254), DATSTA char(254), NATCON char(254), NOBJNM char(254), OBJNAM char(254), PEREND char(254), PERSTA char(254), STATUS char(254), VERACC double, VERLEN double, INFORM char(254), NINFOM char(254), NTXTDS char(254), SCAMAX integer, SCAMIN integer, TXTDSC char(254),
      RECDAT char(254), RECIND char(254), SORDAT char(254), SORIND char(254)
    -> Junction
UNSARE (reader S57_2)
    attributes: RCID integer, PRIM integer16, GRUP integer16, OBJL integer, RVER integer16, AGEN integer, FIDN integer, FIDS integer, LNAM char(16), LNAM_REFS{} char(16), FFPT_RIND{} integer16, INFORM char(254), NINFOM char(254), NTXTDS char(254), SCAMAX integer, SCAMIN integer, TXTDSC char(254), RECDAT char(254), RECIND char(254), SORDAT char(254), SORIND char(254)
    -> Junction

Bookmark: Reader Feature Types
LNDMRK (reader S57_1)
    attributes: RCID integer, PRIM integer16, GRUP integer16, OBJL integer, RVER integer16, AGEN integer, FIDN integer, FIDS integer, LNAM char(16), LNAM_REFS{} char(16), FFPT_RIND{} integer16, CATLMK char(254), COLOUR char(254), COLPAT char(254), CONDTN integer, CONRAD integer, CONVIS integer, ELEVAT double, FUNCTN char(254), HEIGHT double, NATCON char(254), NOBJNM char(254), OBJNAM char(254), STATUS char(254), VERACC double, VERDAT integer, VERLEN double, INFORM char(254), NINFOM char(254), NTXTDS char(254),
      PICREP char(254), SCAMAX integer, SCAMIN integer, TXTDSC char(254), RECDAT char(254), RECIND char(254), SORDAT char(254), SORIND char(254)
    -> SpatialFilter [Candidate]
BUISGL (reader S57_1)
    attributes: RCID integer, PRIM integer16, GRUP integer16, OBJL integer, RVER integer16, AGEN integer, FIDN integer, FIDS integer, LNAM char(16), LNAM_REFS{} char(16), FFPT_RIND{} integer16, BUISHP integer, COLOUR char(254), COLPAT char(254), CONDTN integer, CONRAD integer, CONVIS integer, ELEVAT double, FUNCTN char(254), HEIGHT double, NATCON char(254), NOBJNM char(254), OBJNAM char(254), STATUS char(254), VERACC double, VERDAT integer, VERLEN double, INFORM char(254), NINFOM char(254), NTXTDS char(254),
      PICREP char(254), SCAMAX integer, SCAMIN integer, TXTDSC char(254), RECDAT char(254), RECIND char(254), SORDAT char(254), SORIND char(254)
    -> SpatialFilter_2 [Candidate]
SILTNK (reader S57_1)
    attributes: RCID integer, PRIM integer16, GRUP integer16, OBJL integer, RVER integer16, AGEN integer, FIDN integer, FIDS integer, LNAM char(16), LNAM_REFS{} char(16), FFPT_RIND{} integer16, BUISHP integer, CATSIL integer, COLOUR char(254), COLPAT char(254), CONDTN integer, CONRAD integer, CONVIS integer, ELEVAT double, HEIGHT double, NATCON char(254), NOBJNM char(254), OBJNAM char(254), PRODCT char(254), STATUS char(254), VERACC double, VERDAT integer, VERLEN double, INFORM char(254), NINFOM char(254),
      NTXTDS char(254), PICREP char(254), SCAMAX integer, SCAMIN integer, TXTDSC char(254), RECDAT char(254), RECIND char(254), SORDAT char(254), SORIND char(254)
    -> SpatialFilter_3 [Candidate]
FORSTC (reader S57_1)
    attributes: RCID integer, PRIM integer16, GRUP integer16, OBJL integer, RVER integer16, AGEN integer, FIDN integer, FIDS integer, LNAM char(16), LNAM_REFS{} char(16), FFPT_RIND{} integer16, CATFOR integer, CONDTN integer, CONRAD integer, CONVIS integer, HEIGHT double, NATCON char(254), NOBJNM char(254), OBJNAM char(254), VERACC double, VERDAT integer, VERLEN double, INFORM char(254), NINFOM char(254), NTXTDS char(254), PICREP char(254), SCAMAX integer, SCAMIN integer, TXTDSC char(254), RECDAT char(254),
      RECIND char(254), SORDAT char(254), SORIND char(254)
    -> SpatialFilter_4 [Candidate]
CRANES (reader S57_1)
    attributes: RCID integer, PRIM integer16, GRUP integer16, OBJL integer, RVER integer16, AGEN integer, FIDN integer, FIDS integer, LNAM char(16), LNAM_REFS{} char(16), FFPT_RIND{} integer16, CATCRN integer, COLOUR char(254), COLPAT char(254), CONDTN integer, CONRAD integer, CONVIS integer, HEIGHT double, LIFCAP double, NOBJNM char(254), OBJNAM char(254), ORIENT double, RADIUS double, STATUS char(254), VERACC double, VERCLR double, VERDAT integer, VERLEN double, INFORM char(254), NINFOM char(254),
      NTXTDS char(254), PICREP char(254), SCAMAX integer, SCAMIN integer, TXTDSC char(254), RECDAT char(254), RECIND char(254), SORDAT char(254), SORIND char(254)
    -> SpatialFilter_5 [Candidate]

Bookmark: Spatial Filters
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> FilenamePartExtractor
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> FilenamePartExtractor_2
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> FilenamePartExtractor_3
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> FilenamePartExtractor_4
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS CONTAINS
    USE_BOUNDING_BOX = No
    PASSED -> FilenamePartExtractor_5

Bookmark: Filename Extractor
FilenamePartExtractor
    DIRNAME_ATTR = _dirname
    DIRPATH_ATTR = _dirpath
    EXTENSION_ATTR = _extension
    FULLNAME_ATTR = _filename
    ROOTNAME_ATTR = _rootname
    SRC_ATTR = @Value(DSNM)
    -> AttributeRemover
FilenamePartExtractor_2
    DIRNAME_ATTR = _dirname
    DIRPATH_ATTR = _dirpath
    EXTENSION_ATTR = _extension
    FULLNAME_ATTR = _filename
    ROOTNAME_ATTR = _rootname
    SRC_ATTR = @Value(DSNM)
    -> AttributeRemover_2
FilenamePartExtractor_3
    DIRNAME_ATTR = _dirname
    DIRPATH_ATTR = _dirpath
    EXTENSION_ATTR = _extension
    FULLNAME_ATTR = _filename
    ROOTNAME_ATTR = _rootname
    SRC_ATTR = @Value(DSNM)
    -> AttributeRemover_3
FilenamePartExtractor_4
    DIRNAME_ATTR = _dirname
    DIRPATH_ATTR = _dirpath
    EXTENSION_ATTR = _extension
    FULLNAME_ATTR = _filename
    ROOTNAME_ATTR = _rootname
    SRC_ATTR = @Value(DSNM)
    -> AttributeRemover_4
FilenamePartExtractor_5
    DIRNAME_ATTR = _dirname
    DIRPATH_ATTR = _dirpath
    EXTENSION_ATTR = _extension
    FULLNAME_ATTR = _filename
    ROOTNAME_ATTR = _rootname
    SRC_ATTR = @Value(DSNM)
    -> AttributeRemover_5

Bookmark: Remove Attributes
AttributeRemover
    REMOVE_ATTRS = _dirname,_dirpath,_extension,_filename,_rootname
    -> GeometryFilter_4
    -> GeometryRemover
AttributeRemover_2
    REMOVE_ATTRS = _dirname,_dirpath,_extension,_filename,_rootname
    -> GeometryFilter
    -> GeometryRemover_2
AttributeRemover_3
    REMOVE_ATTRS = _dirname,_dirpath,_extension,_filename,_rootname
    -> GeometryFilter_5
    -> GeometryRemover_3
AttributeRemover_4
    REMOVE_ATTRS = _dirname,_dirpath,_extension,_filename,_rootname
    -> GeometryFilter_3
    -> GeometryRemover_4
AttributeRemover_5
    REMOVE_ATTRS = _dirname,_dirpath,_extension,_filename,_rootname
    -> GeometryFilter_2
    -> GeometryRemover_5

Bookmark: Excel Table
GeometryRemover
    -> LNDMRK (writer XLSXW_3)
LNDMRK (writer XLSXW_3)
    attributes: RCID number(20), PRIM number(20), GRUP number(20), OBJL number(20), RVER number(20), AGEN number(20), FIDN number(20), FIDS number(20), LNAM string(16), LNAM_REFS__ string(16), FFPT_RIND__ number(20), CATLMK string(254), COLOUR string(254), COLPAT string(254), CONDTN number(20), CONRAD number(20), CONVIS number(20), ELEVAT number(20), FUNCTN string(254), HEIGHT number(20), NATCON string(254), NOBJNM string(254), OBJNAM string(254), STATUS string(254), VERACC number(20), VERDAT number(20), VERLEN number(20), INFORM string(254), NINFOM string(254), NTXTDS string(254),
      PICREP string(254), SCAMAX number(20), SCAMIN number(20), TXTDSC string(254), RECDAT string(254), RECIND string(254), SORDAT string(254), SORIND string(254), DSNM string(12)

Bookmark: Writer Feature Types
LNDMRK_point (writer SHAPEFILE_1)
    attributes: LNAM_REFS_ char(16), FFPT_RIND_ short, RCID long, PRIM short, GRUP short, OBJL long, RVER short, AGEN long, FIDN long, FIDS long, LNAM char(16), CATLMK char(254), COLOUR char(254), COLPAT char(254), CONDTN long, CONRAD long, CONVIS long, ELEVAT double, FUNCTN char(254), HEIGHT double, NATCON char(254), NOBJNM char(254), OBJNAM char(254), STATUS char(254), VERACC double, VERDAT long, VERLEN double, INFORM char(254), NINFOM char(254), NTXTDS char(254),
      PICREP char(254), SCAMAX long, SCAMIN long, TXTDSC char(254), RECDAT char(254), RECIND char(254), SORDAT char(254), SORIND char(254), DSNM char(12), _predicate char(200)
LNDMRK_line (writer SHAPEFILE_1)
    attributes: LNAM_REFS_ char(16), FFPT_RIND_ short, RCID long, PRIM short, GRUP short, OBJL long, RVER short, AGEN long, FIDN long, FIDS long, LNAM char(16), CATLMK char(254), COLOUR char(254), COLPAT char(254), CONDTN long, CONRAD long, CONVIS long, ELEVAT double, FUNCTN char(254), HEIGHT double, NATCON char(254), NOBJNM char(254), OBJNAM char(254), STATUS char(254), VERACC double, VERDAT long, VERLEN double, INFORM char(254), NINFOM char(254), NTXTDS char(254),
      PICREP char(254), SCAMAX long, SCAMIN long, TXTDSC char(254), RECDAT char(254), RECIND char(254), SORDAT char(254), SORIND char(254), DSNM char(12), _predicate char(200)
LNDMRK_polygon (writer SHAPEFILE_1)
    attributes: LNAM_REFS_ char(16), FFPT_RIND_ short, RCID long, PRIM short, GRUP short, OBJL long, RVER short, AGEN long, FIDN long, FIDS long, LNAM char(16), CATLMK char(254), COLOUR char(254), COLPAT char(254), CONDTN long, CONRAD long, CONVIS long, ELEVAT double, FUNCTN char(254), HEIGHT double, NATCON char(254), NOBJNM char(254), OBJNAM char(254), STATUS char(254), VERACC double, VERDAT long, VERLEN double, INFORM char(254), NINFOM char(254), NTXTDS char(254),
      PICREP char(254), SCAMAX long, SCAMIN long, TXTDSC char(254), RECDAT char(254), RECIND char(254), SORDAT char(254), SORIND char(254), DSNM char(12), _predicate char(200)
BUISGL_point (writer SHAPEFILE_1)
    attributes: LNAM_REFS_ char(16), FFPT_RIND_ short, RCID long, PRIM short, GRUP short, OBJL long, RVER short, AGEN long, FIDN long, FIDS long, LNAM char(16), BUISHP long, COLOUR char(254), COLPAT char(254), CONDTN long, CONRAD long, CONVIS long, ELEVAT double, FUNCTN char(254), HEIGHT double, NATCON char(254), NOBJNM char(254), OBJNAM char(254), STATUS char(254), VERACC double, VERDAT long, VERLEN double, INFORM char(254), NINFOM char(254), NTXTDS char(254),
      PICREP char(254), SCAMAX long, SCAMIN long, TXTDSC char(254), RECDAT char(254), RECIND char(254), SORDAT char(254), SORIND char(254), DSNM char(12), _predicate char(200)
BUISGL_polygon (writer SHAPEFILE_1)
    attributes: LNAM_REFS_ char(16), FFPT_RIND_ short, RCID long, PRIM short, GRUP short, OBJL long, RVER short, AGEN long, FIDN long, FIDS long, LNAM char(16), BUISHP long, COLOUR char(254), COLPAT char(254), CONDTN long, CONRAD long, CONVIS long, ELEVAT double, FUNCTN char(254), HEIGHT double, NATCON char(254), NOBJNM char(254), OBJNAM char(254), STATUS char(254), VERACC double, VERDAT long, VERLEN double, INFORM char(254), NINFOM char(254), NTXTDS char(254),
      PICREP char(254), SCAMAX long, SCAMIN long, TXTDSC char(254), RECDAT char(254), RECIND char(254), SORDAT char(254), SORIND char(254), DSNM char(12), _predicate char(200)
SILTNK_point (writer SHAPEFILE_1)
    attributes: LNAM_REFS_ char(16), FFPT_RIND_ short, RCID long, PRIM short, GRUP short, OBJL long, RVER short, AGEN long, FIDN long, FIDS long, LNAM char(16), BUISHP long, CATSIL long, COLOUR char(254), COLPAT char(254), CONDTN long, CONRAD long, CONVIS long, ELEVAT double, HEIGHT double, NATCON char(254), NOBJNM char(254), OBJNAM char(254), PRODCT char(254), STATUS char(254), VERACC double, VERDAT long, VERLEN double, INFORM char(254), NINFOM char(254),
      NTXTDS char(254), PICREP char(254), SCAMAX long, SCAMIN long, TXTDSC char(254), RECDAT char(254), RECIND char(254), SORDAT char(254), SORIND char(254), DSNM char(12), _predicate char(200)
SILTNK_polygon (writer SHAPEFILE_1)
    attributes: LNAM_REFS_ char(16), FFPT_RIND_ short, RCID long, PRIM short, GRUP short, OBJL long, RVER short, AGEN long, FIDN long, FIDS long, LNAM char(16), BUISHP long, CATSIL long, COLOUR char(254), COLPAT char(254), CONDTN long, CONRAD long, CONVIS long, ELEVAT double, HEIGHT double, NATCON char(254), NOBJNM char(254), OBJNAM char(254), PRODCT char(254), STATUS char(254), VERACC double, VERDAT long, VERLEN double, INFORM char(254), NINFOM char(254),
      NTXTDS char(254), PICREP char(254), SCAMAX long, SCAMIN long, TXTDSC char(254), RECDAT char(254), RECIND char(254), SORDAT char(254), SORIND char(254), DSNM char(12), _predicate char(200)
FORSTC_point (writer SHAPEFILE_1)
    attributes: LNAM_REFS_ char(16), FFPT_RIND_ short, RCID long, PRIM short, GRUP short, OBJL long, RVER short, AGEN long, FIDN long, FIDS long, LNAM char(16), CATFOR long, CONDTN long, CONRAD long, CONVIS long, HEIGHT double, NATCON char(254), NOBJNM char(254), OBJNAM char(254), VERACC double, VERDAT long, VERLEN double, INFORM char(254), NINFOM char(254), NTXTDS char(254), PICREP char(254), SCAMAX long, SCAMIN long, TXTDSC char(254), RECDAT char(254),
      RECIND char(254), SORDAT char(254), SORIND char(254), DSNM char(12), _predicate char(200)
FORSTC_line (writer SHAPEFILE_1)
    attributes: LNAM_REFS_ char(16), FFPT_RIND_ short, RCID long, PRIM short, GRUP short, OBJL long, RVER short, AGEN long, FIDN long, FIDS long, LNAM char(16), CATFOR long, CONDTN long, CONRAD long, CONVIS long, HEIGHT double, NATCON char(254), NOBJNM char(254), OBJNAM char(254), VERACC double, VERDAT long, VERLEN double, INFORM char(254), NINFOM char(254), NTXTDS char(254), PICREP char(254), SCAMAX long, SCAMIN long, TXTDSC char(254), RECDAT char(254),
      RECIND char(254), SORDAT char(254), SORIND char(254), DSNM char(12), _predicate char(200)
FORSTC_polygon (writer SHAPEFILE_1)
    attributes: LNAM_REFS_ char(16), FFPT_RIND_ short, RCID long, PRIM short, GRUP short, OBJL long, RVER short, AGEN long, FIDN long, FIDS long, LNAM char(16), CATFOR long, CONDTN long, CONRAD long, CONVIS long, HEIGHT double, NATCON char(254), NOBJNM char(254), OBJNAM char(254), VERACC double, VERDAT long, VERLEN double, INFORM char(254), NINFOM char(254), NTXTDS char(254), PICREP char(254), SCAMAX long, SCAMIN long, TXTDSC char(254), RECDAT char(254),
      RECIND char(254), SORDAT char(254), SORIND char(254), DSNM char(12), _predicate char(200)
CRANES_point (writer SHAPEFILE_1)
    attributes: LNAM_REFS_ char(16), FFPT_RIND_ short, RCID long, PRIM short, GRUP short, OBJL long, RVER short, AGEN long, FIDN long, FIDS long, LNAM char(16), CATCRN long, COLOUR char(254), COLPAT char(254), CONDTN long, CONRAD long, CONVIS long, HEIGHT double, LIFCAP double, NOBJNM char(254), OBJNAM char(254), ORIENT double, RADIUS double, STATUS char(254), VERACC double, VERCLR double, VERDAT long, VERLEN double, INFORM char(254), NINFOM char(254),
      NTXTDS char(254), PICREP char(254), SCAMAX long, SCAMIN long, TXTDSC char(254), RECDAT char(254), RECIND char(254), SORDAT char(254), SORIND char(254), DSNM char(12), _predicate char(200)
CRANES_polygon (writer SHAPEFILE_1)
    attributes: LNAM_REFS_ char(16), FFPT_RIND_ short, RCID long, PRIM short, GRUP short, OBJL long, RVER short, AGEN long, FIDN long, FIDS long, LNAM char(16), CATCRN long, COLOUR char(254), COLPAT char(254), CONDTN long, CONRAD long, CONVIS long, HEIGHT double, LIFCAP double, NOBJNM char(254), OBJNAM char(254), ORIENT double, RADIUS double, STATUS char(254), VERACC double, VERCLR double, VERDAT long, VERLEN double, INFORM char(254), NINFOM char(254),
      NTXTDS char(254), PICREP char(254), SCAMAX long, SCAMIN long, TXTDSC char(254), RECDAT char(254), RECIND char(254), SORDAT char(254), SORIND char(254), DSNM char(12), _predicate char(200)
